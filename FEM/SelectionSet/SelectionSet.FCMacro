# -*- coding: utf-8 -*-
"""
SelectionSet macro entry point.

Run this file as a macro in FreeCAD to load the SelectionSet toolbar and
optional test geometry.
"""
__Name__ = "SelectionSet"
__Version__ = "1.1.0"
__title__ = "FreeCAD macro to create SelectionSets and SelectionSetLinks"
__author__ = "HoWil"
__url__ = "https://github.com/HoWilgh/FreeCAD-macros/tree/master/FEM/SelectionSet"
__Files__ = [
    "selection_set_core.py",
    "selection_set_tests.py",
    "icons/SelectionSet.svg",
    "icons/SelectionSetLink.svg",
]

import FreeCAD
import importlib
import os
import sys

_macro_dir = os.path.dirname(os.path.abspath(__file__))
if _macro_dir not in sys.path:
    sys.path.insert(0, _macro_dir)

import selection_set_core
import selection_set_tests

importlib.reload(selection_set_core)
importlib.reload(selection_set_tests)

_version = getattr(selection_set_core, "__version__", "?")
print("=" * 60)
print("  SelectionSet macro - RUN STARTED  (version %s)" % _version)
print("=" * 60)

selection_set_core._detach_selectionset_observer(quiet=True)
selection_set_core.add_selectionset_button_to_toolbar()
selection_set_tests.add_tests_pulldown_to_toolbar()

if selection_set_core.USE_SELECTION_OBSERVER:
    selection_set_core._attach_selectionset_observer()
    print(
        "SelectionSet macro loaded: Observer enabled (single-click expands). "
        "Buttons on 'Selection_tools' toolbar."
    )
else:
    print(
        "SelectionSet macro loaded: Select a SelectionSet in the tree, then "
        "click 'Expand SelectionSet' on the toolbar; or double-click/right-click "
        "the SelectionSet in the tree."
    )
print(
    "Next steps: Use the 'Tests' pulldown (Run Test 1, Build test geometry, "
    "Run Test 3, Run all tests, FEM beam example)."
)
